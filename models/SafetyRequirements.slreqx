# SafetyRequirements

## #1: در صورت رسیدن به دماهای آستانه، بخاری باید مدیریت شود تا از مصرف توان بیش از حد جلوگیری شود. (Functional)

## #2: اگر سنسور دمایی خراب شود، سیستم باید از آخرین داده‌های معتبر خود استفاده کند. (Functional)

## #3: پارامترهای کنترلی (مانند آستانه‌ها) نباید در حین کار تغییر کنند. (Functional)
