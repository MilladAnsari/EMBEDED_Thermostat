# FunctionalRequirements

## #1: دمای هر اتاق باید بین 15 تا 20 درجه نگه داشته شود. (Functional)

## #2: حداکثر دو بخاری می‌توانند به طور همزمان روشن باشند. (Functional)

## #3: هر اتاق حداکثر می‌تواند یک بخاری داشته‌باشد. (Functional)

## #4: بخاری‌ها بر اساس شرایط لازم، باید بین اتاق‌ها جابه‌حا شوند. (Functional)
بخاری اتاق j به اتاق i منتقل می‌شود اگر:
اتاق i بخاری نداشته باشد
اتاق j بخاری داشته باشد
دما xi <= get(i) باشد
اختلاف xj - xi >= diff(i) باشد

## #5: اگر دمای از آستانه‌ی پایین کمتر شود، بخاری با بیشترین توان شروع به کار می‌کند. (Functional)

## #6: اگر دما از آستانه‌ی بالا بیشتر شود، بخاری خاموش می‌شود. (Functional)

## #7: طبق رابطه‌ی داده شده، دمای بیرون در کارکرد سیستم تاثیرگذار است. (Functional)

## #8: طبق رابطه‌ی داده شده، دمای اتاق‌ها بر هم دیگر اثر می‌گذارند. (Functional)

## #9: سیستم باید توسط یک بخش ایمنی، خروجی را کنترل کند. (Functional)
