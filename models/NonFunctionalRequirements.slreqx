# NonFunctionalRequirements

## #1: سیستم باید در کمتر از 5 ثانیه به تغییرات دما واکنش دهد. (Functional)

## #2: سیستم نباید نوسان شدید دمایی ایجاد کند (مخصوصا در مرز آستانه‌ها) (Functional)

## #3: طراحی باید توانایی اضافه کردن اتاق‌های بیشتر را داشته باشد. (Functional)
